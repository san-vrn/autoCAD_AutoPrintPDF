Attribute VB_Name = "Module1"

' печать блоков-форматов в PDF
Sub PlotByPDF()
 
 'Декларация переменных
    Dim objEnt As AcadEntity
    Dim objBRef As AcadBlockReference
    Dim pt1 As Variant
    Dim pt2(0 To 1) As Double
    Dim i As String
    Dim VSP As Integer
    Dim MyCanonical As Integer
    Dim docName As String
    
    
    'выбираем параметры для печати
    MyCanonical = 0 'задаём параметр соответствия профиля печати
    i = ThisDrawing.Utility.GetString(1, vbCrLf & "Введите номер первого чертежа") ' вводим номер первого чертежа для последовательного сохранения
    
    VSP = ThisDrawing.Utility.GetString(0, vbCrLf & "Выберите тип печати: 1 - монохром, 2 - цветной ") 'Выбираем тип печати
    
    'Условие для VSP
    If VSP < 1 Or VSP > 2 Then
        MsgBox "Значение может быть 1 или 2", vbExclamation
        Exit Sub
    End If
    
    i = i - 1 'костыль №1
        
    ' Создаем выбор рамкой
    On Error Resume Next
    ThisDrawing.SelectionSets("SS").Delete
    Set ss = ThisDrawing.SelectionSets.Add("SS")
    ss.SelectOnScreen
        
    ' Работаем по имени блока
    For Each objEnt In ss
    If objEnt.ObjectName = "AcDbBlockReference" Then
    Set objBRef = objEnt
  
            'A4
        If objBRef.EffectiveName = "A4" Then
            pt1 = objBRef.InsertionPoint
            pt1 = ThisDrawing.Utility.TranslateCoordinates(pt1, acWorld, acDisplayDCS, False)
            ReDim Preserve pt1(0 To 1)
            pt2(0) = pt1(0) + 210 'Ширина
            pt2(1) = pt1(1) + 297 'Высота
            MyCanonical = 4
            docName = ThisDrawing.FullName
            i = i + 1
            PolyPlot docName + CStr(i + ".pdf"), pt1, pt2, MyCanonical, VSP 'передаём в функцию ПолиПлот следующие значения переменных
        End If
            'A4x3
        If objBRef.EffectiveName = "A4x3" Then
            pt1 = objBRef.InsertionPoint
            pt1 = ThisDrawing.Utility.TranslateCoordinates(pt1, acWorld, acDisplayDCS, False)
            ReDim Preserve pt1(0 To 1)
            pt2(0) = pt1(0) + 630 'Ширина
            pt2(1) = pt1(1) + 297 'Высота
            MyCanonical = 43
            docName = ThisDrawing.FullName
            i = i + 1
            PolyPlot docName + CStr(i + ".pdf"), pt1, pt2, MyCanonical, VSP
        End If
            'A4x4
        If objBRef.EffectiveName = "A4x4" Then
            pt1 = objBRef.InsertionPoint
            pt1 = ThisDrawing.Utility.TranslateCoordinates(pt1, acWorld, acDisplayDCS, False)
            ReDim Preserve pt1(0 To 1)
            pt2(0) = pt1(0) + 840 'Ширина
            pt2(1) = pt1(1) + 297 'Высота
            MyCanonical = 44
            docName = ThisDrawing.FullName
            i = i + 1
            PolyPlot docName + CStr(i + ".pdf"), pt1, pt2, MyCanonical, VSP
        End If
        
        'A4x5
        If objBRef.EffectiveName = "A4x5" Then
            pt1 = objBRef.InsertionPoint
            pt1 = ThisDrawing.Utility.TranslateCoordinates(pt1, acWorld, acDisplayDCS, False)
            ReDim Preserve pt1(0 To 1)
            pt2(0) = pt1(0) + 1050 'Ширина
            pt2(1) = pt1(1) + 297 'Высота
            MyCanonical = 45
            docName = ThisDrawing.FullName
            i = i + 1
            PolyPlot docName + CStr(i + ".pdf"), pt1, pt2, MyCanonical, VSP
        End If
        'A4x6
        If objBRef.EffectiveName = "A4x6" Then
            pt1 = objBRef.InsertionPoint
            pt1 = ThisDrawing.Utility.TranslateCoordinates(pt1, acWorld, acDisplayDCS, False)
            ReDim Preserve pt1(0 To 1)
            pt2(0) = pt1(0) + 1260 'Ширина
            pt2(1) = pt1(1) + 297 'Высота
            MyCanonical = 46
            docName = ThisDrawing.FullName
            i = i + 1
            PolyPlot docName + CStr(i + ".pdf"), pt1, pt2, MyCanonical, VSP
        End If
            'A4x7
        If objBRef.EffectiveName = "A4x7" Then
            pt1 = objBRef.InsertionPoint
            pt1 = ThisDrawing.Utility.TranslateCoordinates(pt1, acWorld, acDisplayDCS, False)
            ReDim Preserve pt1(0 To 1)
            pt2(0) = pt1(0) + 1470 'Ширина
            pt2(1) = pt1(1) + 297 'Высота
            MyCanonical = 47
            docName = ThisDrawing.FullName
            i = i + 1
            PolyPlot docName + CStr(i + ".pdf"), pt1, pt2, MyCanonical, VSP
        End If
            'A4x8
        If objBRef.EffectiveName = "A4x8" Then
            pt1 = objBRef.InsertionPoint
            pt1 = ThisDrawing.Utility.TranslateCoordinates(pt1, acWorld, acDisplayDCS, False)
            ReDim Preserve pt1(0 To 1)
            pt2(0) = pt1(0) + 1680 'Ширина
            pt2(1) = pt1(1) + 297 'Высота
            MyCanonical = 48
            docName = ThisDrawing.FullName
            i = i + 1
            PolyPlot docName + CStr(i + ".pdf"), pt1, pt2, MyCanonical, VSP
        End If
            'A4x9
        If objBRef.EffectiveName = "A4x9" Then
            pt1 = objBRef.InsertionPoint
            pt1 = ThisDrawing.Utility.TranslateCoordinates(pt1, acWorld, acDisplayDCS, False)
            ReDim Preserve pt1(0 To 1)
            pt2(0) = pt1(0) + 1890 'Ширина
            pt2(1) = pt1(1) + 297 'Высота
            MyCanonical = 49
            docName = ThisDrawing.FullName
            i = i + 1
            PolyPlot docName + CStr(i + ".pdf"), pt1, pt2, MyCanonical, VSP
        End If
            'A4x10
        If objBRef.EffectiveName = "A4x10" Then
            pt1 = objBRef.InsertionPoint
            pt1 = ThisDrawing.Utility.TranslateCoordinates(pt1, acWorld, acDisplayDCS, False)
            ReDim Preserve pt1(0 To 1)
            pt2(0) = pt1(0) + 2100 'Ширина
            pt2(1) = pt1(1) + 297 'Высота
            MyCanonical = 410
           docName = ThisDrawing.FullName
            i = i + 1
            PolyPlot docName + CStr(i + ".pdf"), pt1, pt2, MyCanonical, VSP
        End If
            'A4x11
        If objBRef.EffectiveName = "A4x11" Then
            pt1 = objBRef.InsertionPoint
            pt1 = ThisDrawing.Utility.TranslateCoordinates(pt1, acWorld, acDisplayDCS, False)
            ReDim Preserve pt1(0 To 1)
            pt2(0) = pt1(0) + 2310 'Ширина
            pt2(1) = pt1(1) + 297 'Высота
            MyCanonical = 411
            docName = ThisDrawing.FullName
            i = i + 1
            PolyPlot docName + CStr(i + ".pdf"), pt1, pt2, MyCanonical, VSP
        End If
            'A4x12
        If objBRef.EffectiveName = "A4x12" Then
            pt1 = objBRef.InsertionPoint
            pt1 = ThisDrawing.Utility.TranslateCoordinates(pt1, acWorld, acDisplayDCS, False)
            ReDim Preserve pt1(0 To 1)
            pt2(0) = pt1(0) + 2520 'Ширина
            pt2(1) = pt1(1) + 297 'Высота
            MyCanonical = 412
            docName = ThisDrawing.FullName
            i = i + 1
            PolyPlot docName + CStr(i + ".pdf"), pt1, pt2, MyCanonical, VSP
        End If
            'A4x13
        If objBRef.EffectiveName = "A4x13" Then
            pt1 = objBRef.InsertionPoint
            pt1 = ThisDrawing.Utility.TranslateCoordinates(pt1, acWorld, acDisplayDCS, False)
            ReDim Preserve pt1(0 To 1)
            pt2(0) = pt1(0) + 2730 'Ширина
            pt2(1) = pt1(1) + 297 'Высота
            MyCanonical = 413
            docName = ThisDrawing.FullName
            i = i + 1
            PolyPlot docName + CStr(i + ".pdf"), pt1, pt2, MyCanonical, VSP
        End If
            'A4x14
        If objBRef.EffectiveName = "A4x14" Then
            pt1 = objBRef.InsertionPoint
            pt1 = ThisDrawing.Utility.TranslateCoordinates(pt1, acWorld, acDisplayDCS, False)
            ReDim Preserve pt1(0 To 1)
            pt2(0) = pt1(0) + 2940 'Ширина
            pt2(1) = pt1(1) + 297 'Высота
            MyCanonical = 414
            docName = ThisDrawing.FullName
            i = i + 1
            PolyPlot docName + CStr(i + ".pdf"), pt1, pt2, MyCanonical, VSP
        End If
            'A4x15
        If objBRef.EffectiveName = "A4x15" Then
            pt1 = objBRef.InsertionPoint
            pt1 = ThisDrawing.Utility.TranslateCoordinates(pt1, acWorld, acDisplayDCS, False)
            ReDim Preserve pt1(0 To 1)
            pt2(0) = pt1(0) + 3150 'Ширина
            pt2(1) = pt1(1) + 297 'Высота
            MyCanonical = 415
            docName = ThisDrawing.FullName
            i = i + 1
            PolyPlot docName + CStr(i + ".pdf"), pt1, pt2, MyCanonical, VSP
        End If
            'A3
        If objBRef.EffectiveName = "A3" Then
            pt1 = objBRef.InsertionPoint
            pt1 = ThisDrawing.Utility.TranslateCoordinates(pt1, acWorld, acDisplayDCS, False)
            ReDim Preserve pt1(0 To 1)
            pt2(0) = pt1(0) + 420 'Ширина
            pt2(1) = pt1(1) + 297 'Высота
            MyCanonical = 3
            docName = ThisDrawing.FullName
            i = i + 1
            PolyPlot docName + CStr(i + ".pdf"), pt1, pt2, MyCanonical, VSP
        End If
            'A3x2
        If objBRef.EffectiveName = "A3x2" Then
            pt1 = objBRef.InsertionPoint
            pt1 = ThisDrawing.Utility.TranslateCoordinates(pt1, acWorld, acDisplayDCS, False)
            ReDim Preserve pt1(0 To 1)
            pt2(0) = pt1(0) + 594 'Ширина
            pt2(1) = pt1(1) + 420 'Высота
            MyCanonical = 32
            docName = ThisDrawing.FullName
            i = i + 1
            PolyPlot docName + CStr(i + ".pdf"), pt1, pt2, MyCanonical, VSP
        End If
            'A3x3
        If objBRef.EffectiveName = "A3x3" Then
            pt1 = objBRef.InsertionPoint
            pt1 = ThisDrawing.Utility.TranslateCoordinates(pt1, acWorld, acDisplayDCS, False)
            ReDim Preserve pt1(0 To 1)
            pt2(0) = pt1(0) + 891 'Ширина
            pt2(1) = pt1(1) + 420 'Высота
            MyCanonical = 33
            docName = ThisDrawing.FullName
            i = i + 1
            PolyPlot docName + CStr(i + ".pdf"), pt1, pt2, MyCanonical, VSP
        End If
            'A3x4
        If objBRef.EffectiveName = "A3x4" Then
            pt1 = objBRef.InsertionPoint
            pt1 = ThisDrawing.Utility.TranslateCoordinates(pt1, acWorld, acDisplayDCS, False)
            ReDim Preserve pt1(0 To 1)
            pt2(0) = pt1(0) + 1188 'Ширина
            pt2(1) = pt1(1) + 420 'Высота
            MyCanonical = 34
            docName = ThisDrawing.FullName
            i = i + 1
            PolyPlot docName + CStr(i + ".pdf"), pt1, pt2, MyCanonical, VSP
        End If
            'A3x5
        If objBRef.EffectiveName = "A3x5" Then
            pt1 = objBRef.InsertionPoint
            pt1 = ThisDrawing.Utility.TranslateCoordinates(pt1, acWorld, acDisplayDCS, False)
            ReDim Preserve pt1(0 To 1)
            pt2(0) = pt1(0) + 1485 'Ширина
            pt2(1) = pt1(1) + 420 'Высота
            MyCanonical = 35
            docName = ThisDrawing.FullName
            i = i + 1
            PolyPlot docName + CStr(i + ".pdf"), pt1, pt2, MyCanonical, VSP
        End If
            'A3x6
        If objBRef.EffectiveName = "A3x6" Then
            pt1 = objBRef.InsertionPoint
            pt1 = ThisDrawing.Utility.TranslateCoordinates(pt1, acWorld, acDisplayDCS, False)
            ReDim Preserve pt1(0 To 1)
            pt2(0) = pt1(0) + 1782 'Ширина
            pt2(1) = pt1(1) + 420 'Высота
            MyCanonical = 36
            docName = ThisDrawing.FullName
            i = i + 1
            PolyPlot docName + CStr(i + ".pdf"), pt1, pt2, MyCanonical, VSP
        End If
            'A3x7
        If objBRef.EffectiveName = "A3x7" Then
            pt1 = objBRef.InsertionPoint
            pt1 = ThisDrawing.Utility.TranslateCoordinates(pt1, acWorld, acDisplayDCS, False)
            ReDim Preserve pt1(0 To 1)
            pt2(0) = pt1(0) + 2079 'Ширина
            pt2(1) = pt1(1) + 420 'Высота
            MyCanonical = 37
            docName = ThisDrawing.FullName
            i = i + 1
            PolyPlot docName + CStr(i + ".pdf"), pt1, pt2, MyCanonical, VSP
        End If
            'A3x8
        If objBRef.EffectiveName = "A3x8" Then
            pt1 = objBRef.InsertionPoint
            pt1 = ThisDrawing.Utility.TranslateCoordinates(pt1, acWorld, acDisplayDCS, False)
            ReDim Preserve pt1(0 To 1)
            pt2(0) = pt1(0) + 2376 'Ширина
            pt2(1) = pt1(1) + 420 'Высота
            MyCanonical = 38
            docName = ThisDrawing.FullName
            i = i + 1
            PolyPlot docName + CStr(i + ".pdf"), pt1, pt2, MyCanonical, VSP
        End If
        'A3x9
        If objBRef.EffectiveName = "A3x9" Then
            pt1 = objBRef.InsertionPoint
            pt1 = ThisDrawing.Utility.TranslateCoordinates(pt1, acWorld, acDisplayDCS, False)
            ReDim Preserve pt1(0 To 1)
            pt2(0) = pt1(0) + 2673 'Ширина
            pt2(1) = pt1(1) + 420 'Высота
            MyCanonical = 39
            docName = ThisDrawing.FullName
            i = i + 1
            PolyPlot docName + CStr(i + ".pdf"), pt1, pt2, MyCanonical, VSP
        End If
        'A3x10
        If objBRef.EffectiveName = "A3x10" Then
            pt1 = objBRef.InsertionPoint
            pt1 = ThisDrawing.Utility.TranslateCoordinates(pt1, acWorld, acDisplayDCS, False)
            ReDim Preserve pt1(0 To 1)
            pt2(0) = pt1(0) + 2970 'Ширина
            pt2(1) = pt1(1) + 420 'Высота
            MyCanonical = 310
            docName = ThisDrawing.FullName
            i = i + 1
            
            PolyPlot docName + CStr(i + ".pdf"), pt1, pt2, MyCanonical, VSP
        End If
    End If
    Next
    
End Sub
Sub PolyPlot(strFileName As String, pt1 As Variant, pt2 As Variant, MyCanonical As Variant, VSP As Variant)
 
    ' Декларируем
    Dim Layout As AcadLayout
    
    ' Устанавливаем
    Set Layout = ThisDrawing.ActiveLayout
       
    Layout.RefreshPlotDeviceInfo
           
    ' Настройка печати
    Layout.ConfigName = "DWG to PDF.pc3"
    
    ' Выбор профиля печати в зависимости от размеров листа
    If MyCanonical = 4 Then
    Layout.CanonicalMediaName = "ISO_A4_(297.00_x_210.00_MM)" 'высота х ширина
    End If
    If MyCanonical = 43 Then
    Layout.CanonicalMediaName = "UserDefinedMetric (297.00 x 630.00мм)" 'высота х ширина
    End If
    If MyCanonical = 44 Then
    Layout.CanonicalMediaName = "UserDefinedMetric (297.00 x 840.00мм)" 'высота х ширина
    End If
    If MyCanonical = 45 Then
    Layout.CanonicalMediaName = "UserDefinedMetric (297.00 x 1050.00мм)" 'высота х ширина
    End If
    If MyCanonical = 46 Then
    Layout.CanonicalMediaName = "UserDefinedMetric (297.00 x 1260.00мм)" 'высота х ширина
    End If
     If MyCanonical = 47 Then
    Layout.CanonicalMediaName = "UserDefinedMetric (297.00 x 1470.00мм)" 'высота х ширина
    End If
     If MyCanonical = 48 Then
    Layout.CanonicalMediaName = "UserDefinedMetric (297.00 x 1680.00мм)" 'высота х ширина
    End If
    If MyCanonical = 49 Then
    Layout.CanonicalMediaName = "UserDefinedMetric (297.00 x 1890.00мм)" 'высота х ширина
    End If
    If MyCanonical = 410 Then
    Layout.CanonicalMediaName = "UserDefinedMetric (297.00 x 2100.00мм)" 'высота х ширина
    End If
    If MyCanonical = 411 Then
    Layout.CanonicalMediaName = "UserDefinedMetric (297.00 x 2310.00мм)" 'высота х ширина
    End If
    If MyCanonical = 412 Then
    Layout.CanonicalMediaName = "UserDefinedMetric (297.00 x 2520.00мм)" 'высота х ширина
    End If
    If MyCanonical = 413 Then
    Layout.CanonicalMediaName = "UserDefinedMetric (297.00 x 2730.00мм)" 'высота х ширина
    End If
    If MyCanonical = 414 Then
    Layout.CanonicalMediaName = "UserDefinedMetric (297.00 x 2940.00мм)" 'высота х ширина
    End If
    If MyCanonical = 415 Then
    Layout.CanonicalMediaName = "UserDefinedMetric (297.00 x 3150.00мм)" 'высота х ширина
    End If
    If MyCanonical = 3 Then
    Layout.CanonicalMediaName = "ISO_A3_(297.00_x_420.00_MM)" 'высота х ширина
    End If
    If MyCanonical = 32 Then
    Layout.CanonicalMediaName = "UserDefinedMetric (420.00 x 594.00мм)" 'высота х ширина
    End If
    If MyCanonical = 33 Then
    Layout.CanonicalMediaName = "UserDefinedMetric (420.00 x 891.00мм)" 'высота х ширина
    End If
    If MyCanonical = 34 Then
    Layout.CanonicalMediaName = "UserDefinedMetric (420.00 x 1188.00мм)" 'высота х ширина
    End If
    If MyCanonical = 35 Then
    Layout.CanonicalMediaName = "UserDefinedMetric (420.00 x 1485.00мм)" 'высота х ширина
    End If
    If MyCanonical = 36 Then
    Layout.CanonicalMediaName = "UserDefinedMetric (420.00 x 1782.00мм)" 'высота х ширина
    End If
    If MyCanonical = 37 Then
    Layout.CanonicalMediaName = "UserDefinedMetric (420.00 x 2079.00мм)" 'высота х ширина
    End If
    If MyCanonical = 38 Then
    Layout.CanonicalMediaName = "UserDefinedMetric (420.00 x 2376.00мм)" 'высота х ширина
    End If
    If MyCanonical = 39 Then
    Layout.CanonicalMediaName = "UserDefinedMetric (420.00 x 2673.00мм)" 'высота х ширина
    End If
    If MyCanonical = 310 Then
    Layout.CanonicalMediaName = "UserDefinedMetric (420.00 x 2970.00мм)" 'высота х ширина
    End If
    
    
    ' Настройки печати
    
    Layout.StandardScale = acScaleToFit
    Layout.StyleSheet = "acad.ctb"
    
    ' Устанавливаем рамки, тип окошка, выравнивание по центру(работает на листах (не в модели) только когда PlotType = acWindow)
    Layout.SetWindowToPlot pt1, pt2
    Layout.PlotType = acWindow
    Layout.CenterPlot = True
    
    
    'Устанавливаем фоновую печать на 0
    BackPlot = ThisDrawing.GetVariable("BACKGROUNDPLOT")
    ThisDrawing.SetVariable "BACKGROUNDPLOT", 0
    
    'Выбор цвета печати (монохром или цветная печать)
    If VSP = 2 Then
        Layout.StyleSheet = "acad.ctb"
    Else
        Layout.StyleSheet = "monochrome.ctb"
    End If
    
    ' Отправляем на печать
    Layout.PlotRotation = ac90degrees
    ThisDrawing.Regen acAllViewports
    ThisDrawing.Plot.PlotToFile strFileName
    Application.Dialogs(xlDialogSaveAs).Show
    
    'Устанавливаем фоновую печать на 2
    BackPlot = ThisDrawing.GetVariable("BACKGROUNDPLOT")
    ThisDrawing.SetVariable "BACKGROUNDPLOT", 2
    
End Sub

 Function Savefile(docName As String)
    
    On Error Resume Next
    Dim objShellApp As Object, objFolder As Object, ulFlags
    Dim x As String
    Set objShellApp = CreateObject("Shell.Application")
    'ulFlags = 0 - наиболее часто применяемый. Лучше использовать всегда именно 0
    'ulFlags = 2 - так же можно выбрать файлы
    'ulFlags = 20 - добавляется тестовое поле с отображением имени выбранной папки
    ulFlags = 0
    Set objFolder = objShellApp.BrowseForFolder(0, "Выбрать папку для сохранения", ulFlags, "\\zv-main\scb")  '
    x = objFolder.Self.Path 'записываем в переменную путь к папке
    If Err.Number <> 0 Then
        MsgBox "Папка не выбрана!", vbInformation
    Else
        MsgBox "Выбрана папка: '" & x & "'", vbInformation
    End If
End Function

Sub ShowFolderDialog()
    Dim oFD As FileDialog
    Dim x, lf As Long
    'назначаем переменной ссылку на экземпляр диалога
    Set oFD = Application.FileDialog(msoFileDialogFolderPicker)
    With oFD 'используем короткое обращение к объекту
    'так же можно без oFD
    'With Application.FileDialog(msoFileDialogFolderPicker)
        .Title = "Выбрать папку с отчетами" '"заголовок окна диалога
        .ButtonName = "Выбрать папку"
        .Filters.Clear 'очищаем установленные ранее типы файлов
        .InitialFileName = "C:\Temp\" '"назначаем первую папку отображения
        .InitialView = msoFileDialogViewLargeIcons 'вид диалогового окна(доступно 9 вариантов)
        If oFD.Show = 0 Then Exit Sub 'показывает диалог
        'цикл по коллекции выбранных в диалоге файлов
        x = .SelectedItems(1) 'считываем путь к папке
        MsgBox "Выбрана папка: '" & x & "'", vbInformation, "www.excel-vba.ru"
    End With
End Sub

Attribute VB_Name = "Module2"
:
'---------------------------------------------------------------------------------------
' Procedure : fnGetFolder
' DateTime : 17.08.2006 16:12
' Author : DSonnyh
' Purpose : выбор папки
'---------------------------------------------------------------------------------------
'
Public Function fnGetFolder() As String

Dim WSHShell As Object, objFolder As Object
Dim P1, P2
'Некоторые значения констант:
' P1=0 - отображаются Рабочий стол, Мой компьютер, Сеть и "Корзина"
' P1=1 - "Корзина" не отображается
' P1=2 - "Корзина" отображается, в "Моем компьютере" выводится дополнительно "Панель Управления"
' P2 определяет верхний уровень отображения. Его можно задать как строку символов
' Пример - "C:\". Или числом. Проверено для ХР
' Р2=0 - Рабочий стол P2=10 - Корзина
' P2=1 - Интернет Explorer (недопустимо) P2=11 - Главное меню
' P2=2 - Программы Р2=12 - Рабочий стол
' P2=3 - Панель управления (недопустимо) Р2=13 - Моя музыка
' P2=4 - Принтеры и факсы (недопустимо) Р2=14 - Мои видеозаписи
' P2=5 - Мои Документы Р2=15 - Рабочий стол
' P2=6 - Избранное Р2=16 - Рабочий стол
' P2=7 - Автозагрузка Р2=17 - Мой Компьютер
' P2=8 - недавние Документы Р2=18 - Сетевой окружение
' P2=9 - SendTo Р2=19 - NetHood
' Р2=20 - Fonts Р2=21 - Templates
' Более подробную информацию об объекте можно найти в документации (EN)

On Error GoTo fnGetFolder_Error

P1 = 1
P2 = 0

Set WSHShell = CreateObject("Shell.application")
Set objFolder = WSHShell.BrowseForFolder(10, "Выбор папки", P1, P2)
fnGetFolder = objFolder.Self.Path
' имя папки содержится в objFolders.Title
Set WSHShell = Nothing
Set objFolder = Nothing

On Error GoTo 0
Exit_fnGetFolder:
Exit Function

fnGetFolder_Error:

Set WSHShell = Nothing
Set objFolder = Nothing
Select Case Err.Number
Case 91
fnGetFolder = ""
Resume Exit_fnGetFolder
Case Else
MsgBox "Ошибка " & Err.Number & " (" & Err.Description & ") в процедуре fnGetFolder"
Resume Exit_fnGetFolder
End Select

End Function
